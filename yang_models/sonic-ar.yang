module sonic-ar {      yang-version 1.1;      namespace "http://github.com/sonic-net/sonic-ar";     prefix ar;      import sonic-types {         prefix stypes;     }      import sonic-feature {         prefix feature;     }      import sonic-interface {         prefix interface;         revision-date 2021-03-30;     }      description "Adaptive routing configuration";      typedef ar_fixed_profiles {         type enumeration {             enum ar-cfg-profile0;             enum ar-cfg-profile1;         }     }      container sonic-ar {         container AR_GLOBAL {             description "Adaptive routing global configuration";              container global {                 leaf state {                     type stypes:admin_mode;                     description "Administrative state of the feature";                      /* Uncomment once the transient disablement of the feature during extension upgrade is fixed.                      * must "current() = \"disabled\" or /feature:sonic-feature/feature:FEATURE/feature:FEATURE_LIST[feature:name=\"doai\"]/feature:state = \"enabled\"" {                      *     error-message "Adaptive Routing can be enabled only when doAI is enabled";                      * }                      */                 }                  leaf active_profile {                     type union {                         type leafref {                             path "/ar:sonic-ar/ar:AR_PROFILE/ar:AR_PROFILE_LIST/ar:AR_PROFILE_NAME";                         }                         type ar_fixed_profiles;                     }                     description "Current active profile used by Adaptive Routing";                 }                  leaf link_utilization_threshold_disabled {                     type stypes:boolean_type;                     description "Disables link utilization port grading when set to true";                 }                  leaf link_utilization_threshold {                     type uint8 {                         range "1..100";                     }                     description "Link utilization threashold";                 }             }         }          container AR_PROFILE {             description "Adaptive Routing Profile definitions";              list AR_PROFILE_LIST {                 key "AR_PROFILE_NAME";                  leaf AR_PROFILE_NAME {                     mandatory true;                     type string;                      must "(current() != \"ar-cfg-profile0\" and current() != \"ar-cfg-profile1\")" {                         error-message "ar-cfg-profile0 and ar-cfg-profile1 are reserved names for default profiles";                     }                      description "Name of the AR profile";                 }                  leaf m {                     mandatory true;                     type uint8;                 }                  leaf ctl {                     mandatory true;                     type uint32;                 }                  leaf ctm {                     mandatory true;                     must "current() > ../ctl";                     type uint32;                 }                  leaf cth {                     mandatory true;                     must "current() > ../ctm";                     type uint32;                 }                  leaf bit {                     when "../m = 1";                     type uint32;                 }                  leaf frt {                     mandatory true;                     type uint8;                 }                  leaf but {                     mandatory true;                     type uint8;                 }                  leaf sfe {                     type stypes:boolean_type;                 }                  leaf srf {                     when "../sfe";                     type uint16;                 }                  leaf ste {                     type stypes:boolean_type;                     mandatory true;                 }                  leaf srt {                     when "../ste";                     type uint16;                 }                  leaf ef {                     type stypes:boolean_type;                     mandatory true;                 }                  leaf ecs {                     type uint16 {                         range "64|128|256|512|1024|2048|4096";                     }                 }                  leaf lutd {                     type stypes:boolean_type;                 }                  leaf lut {                     type uint8 {                         range "1..100";                     }                 }                  leaf ibm {                     type uint8 {                         range "0|1";                     }                 }                  leaf pls {                     type uint32;                 }             }         }          container AR_PORT {             list AR_PORT_LIST {                 key "AR_PORT_NAME";                  leaf AR_PORT_NAME {                     type leafref {                         path /interface:sonic-interface/interface:INTERFACE/interface:INTERFACE_LIST/interface:name;                     }                     description "Interface to enable adaptive routing on";                 }             }         }     } }
