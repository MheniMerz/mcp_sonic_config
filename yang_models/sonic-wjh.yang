module sonic-wjh {      namespace "http://github.com/Azure/sonic-wjh";      prefix wjh;      yang-version 1.1;      import sonic-port {         prefix port;     }      description "SONIC-WJH Yang model for SONiC OS";      revision 2022-01-01 {         description "First Revision";     }      typedef channel-name {         type enumeration {             enum forwarding;             enum layer-1;             enum buffer;             enum acl;         }     }      typedef port-name {         type leafref {             path "/port:sonic-port/port:PORT/port:PORT_LIST/port:name";         }     }      container sonic-wjh {          container WJH {              description "What-Just-Happened global configuration";              container global {                  leaf pci_bandwidth {                     type uint8 {                         range 1..100;                     }                     default 50;                 }                  leaf nice_level {                     type int8 {                         range "-20..19";                     }                     default 1;                 }                  leaf mode {                     type enumeration {                         enum debug;                     }                 }             }             /* end of container global */         }         /* end of container WJH */          container WJH_CHANNEL {              description "What-Just-Happened channels configuration";              list WJH_CHANNEL_LIST {                  key "channel";                  leaf channel {                     type channel-name;                 }                  leaf type {                     type enumeration {                         enum "raw_and_aggregate";                         enum "raw";                         enum "aggregate";                     }                     mandatory true;                 }                  leaf-list drop_category_list {                     type enumeration {                         enum L2;                         enum L3;                         enum Tunnel;                         enum L1;                         enum Buffer;                         enum ACL;                     }                     min-elements 1;                 }             }         }         /* end of container WJH_CHANNEL */          container WJH_QUEUE_BUFFER_THRESHOLD {              description "What-Just-Happened port buffer queues congestion threshold configuration";              list WJH_QUEUE_BUFFER_THRESHOLD_LIST {                  key "port_name";                  leaf port_name {                     type port-name;                 }                  leaf threshold_value {                     type uint8 {                         range 0..100;                     }                 }             }          }         /* end of container WJH_QUEUE_BUFFER_THRESHOLD */          container WJH_QUEUE_LATENCY_THRESHOLD {              description "What-Just-Happened port buffer queues latency threshold configuration";              list WJH_QUEUE_LATENCY_THRESHOLD_LIST {                  key "port_name";                  leaf port_name {                     type port-name;                 }                  leaf threshold_value {                     type uint32 {                         range 1..1048575;                     }                 }             }         }         /* end of WJH_QUEUE_LATENCY_THRESHOLD container */     }     /* end of top level container */ } /* end of module sonic-wjh */
