module sonic-doroce {      yang-version 1.1;      namespace "http://github.com/sonic-net/sonic-doroce";     prefix doroce;      import sonic-types {         prefix stypes;     }      import sonic-feature {         prefix feature;     }      description "doRoCE configuration scheme";      container sonic-doroce {         container ROCE {             description "RoCE global configuration";              container global {                 leaf admin_status {                     type stypes:admin_mode;                     description "Administrative state of the feature";                      /* Uncomment once the transient disablement of the feature during extension upgrade is fixed.                      * must "current() = \"disabled\" or /feature:sonic-feature/feature:FEATURE/feature:FEATURE_LIST[feature:name=\"doai\"]/feature:state = \"enabled\"" {                      *     error-message "doRoCE can be enabled only when doAI is enabled";                      * }                      */                 }                  leaf mode {                     type enumeration {                         enum single-ipool;                         enum double-ipool;                         enum None;                     }                 }                  leaf type {                     type enumeration {                         enum lossless;                         enum lossy;                         enum None;                     }                 }                  leaf origin_buffer_model {                     type enumeration {                         enum dynamic;                         enum traditional;                     }                 }             }         }     } }
